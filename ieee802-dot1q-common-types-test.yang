module ieee802-dot1q-common-types-test {
  yang-version "1.1";
  namespace urn:ieee:std:802.1Q:yang:ieee802-dot1q-common-types-test;
  prefix qctt;
  organization
    "Test";
  contact
    "Test contact";
  description
    "Common Types Example";
  revision 2022-11-02 {
    description
      "added yet another type";
    reference
      "yangsters-smansfield-git-examples-1122-v01";
  }
  revision 2022-11-01 {
    description
      "added yet another type";
    reference
      "yangsters-smansfield-git-examples-1122-v01";
  }
  revision 2022-10-31 {
    description
      "added a type for number of foos";
    reference
      "yangsters-smansfield-git-examples-1122-v01";
  }
  revision 2022-10-21 {
    description
      "foobar update";
    reference
      "yangsters-smansfield-git-examples-1122-v01";
  }
  revision 2022-10-01 {
    description
      "Initial revision.";
    reference
      "yangsters-smansfield-git-examples-1122-v01";
  }
  typedef value-range {
    type uint8 {
      range "0..7";
    }
    description
    "A range of values from 0 to 7.";
  }

  typedef bar-value-range {
    type uint64 {
      range "1031..1701";
    }
    description
    "A range of values";
  }

  typedef foo-count-type {
    type uint64;
    description
    "opaque type for counting foos";
  }

  typedef my-unsigned-int-type {
    type uint64;
    description
    "opaque type for unsigned ints";
  }

  typedef my-signed-small-int-type {
    type int8;
    description
    "opaque type for signed small ints";
  }
}
